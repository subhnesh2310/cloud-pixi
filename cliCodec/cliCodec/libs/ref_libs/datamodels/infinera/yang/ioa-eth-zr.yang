module ioa-eth-zr {
    namespace "http://infinera.com/yang/ioa/eth-zr";
    prefix ioa-eth-zr;

    import ioa-common { prefix ioa-common; }
    import ioa-facilities-common { prefix ioa-fac-common; }

    organization "Infinera";

    contact "Infinera Technical Support <techsupport@infinera.com>";

    description "IOA YANG module defining the Eth-ZR facility.";

    revision "2021-12-10" {
        description "YANG Models for Infinera Open API (IOA) for release R5.0";
    }


    grouping eth-zr {
        description "A Digital Coherent 400ZR interface definitions.";

        list eth-zr {
            key name;
            description "Facility describing the Eth-ZR.";

            uses ioa-fac-common:facilities-common-attributes;

            uses ioa-common:arc;

            leaf-list carriers {
                type string { length "1..32"; }
                min-elements 1;
                description "A list of carriers that are bound to this facilities.
                             Possible values can be any card/resources/supported-carriers.";
            }

            leaf rate {
                type ioa-fac-common:rate;
                mandatory true;
                description "
                    Carried signal basic rate class 
                ";
            }

            leaf modulation-format {
                type ioa-fac-common:modulation-format;
                mandatory true;
                description "
                    Current modulation format
                ";
            }

            leaf fec-type {
                type ioa-fac-common:fec-type;
                default ofec;
                description "The FEC type";
            }

            leaf total-time-slots {
                type uint16;
                config false;
                description "The member of the slots to be supported as times of 100G: rate-class/100.";				
            }

            leaf available-time-slots {
                type ioa-common:number-list;
                config false;
                description "A list of time-slots that are available for provisioning new services.";
            }

            leaf fdd-threshold {
                type decimal64{
                    fraction-digits 9;
                    range "0.000000001..0.1"; 
                }
                default 0.0195;
                description "The threshold for FEC Detected Degrade (FDD) alarm.";
            }

            leaf fed-threshold {
                type decimal64{
                    fraction-digits 9;
                    range "0.000000001..0.1"; 
                }
                default 0.0206;
                description "The threshold for FEC Excessive Degrade.";
            }

            uses ioa-fac-common:loopback;
        }
    } 
}
