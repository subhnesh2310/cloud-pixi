module ioa-ots-r {
    namespace "http://infinera.com/yang/ioa/ots-r";
    prefix ioa-ots-r;

    import ioa-common { prefix ioa-common; }
    import ioa-facilities-common { prefix ioa-fac-common; }
    import ioa-l0 { prefix ioa-l0; }
    import ioa-ots { prefix ioa-ots; }


    grouping ots-r {

        list ots-r {
            key "name";
            description "OTS: Optical Transmission Section facility.";

            uses ioa-fac-common:facilities-common-attributes;

            uses ioa-common:arc;

            leaf required-fiber-type-rx {
                type ioa-l0:fiber-type;
                default SSMF;
                description
                    "The required Fiber Type on the DWDM Line, with reference for the Rx fiber.
                    Only of relevance if control-mode = auto.
                    And: when there is no fiber-connection.
                    ";
            }

            leaf configured-fiber-type-rx {
                type ioa-l0:fiber-type;
                config false;
                description
                    "The configured fiber-type-rx on EDFA.
                    If control-mode = auto, it is simply the rx.required-fiber-type.
                    ";
            }

            leaf fiber-length-rx {
                type union {
                    type enumeration {
                        enum unspecified { value 2; description "For OTS (atomatic fiber-length configuration)"; }
                    }
                    type decimal64 {
                        fraction-digits 3;
                        range 0..500.0;
                    }
                }
                units km;
                default 'unspecified';
                description "Receiving Fiber Length";
            }

            leaf configured-fiber-length-rx {
                type ioa-ots:type-of-fiber-length;
                config false;
                description "The configured (receiving) fiber-length-rx on the amplifier.";
            }

            leaf span-loss-receive {
                type ioa-l0:span-loss-info;
                default 99;
                description "The Span Loss at the receiving dwdm-line.";
            }

            leaf span-loss-at-amplifier {
                type ioa-l0:span-loss-info;
                config false;
                description "The Span Loss detected at amplifier, when there is a fiber-connection from/ RPB to the amplifier.";
            }

            uses ioa-ots:external-attenuation-rx {
                refine external-attenuation-rx {
                    description
                        "Loss between Patch panel and the Raman dwdm-line Rx.";
                }
            }

            uses ioa-ots:span-loss-transmit;

            leaf pilot-tone-span-loss {
                type ioa-l0:span-loss-info;
                description
                    "The calculated span-loss based on Pilot Tone.";
            }

            leaf delta-pointloss {
                type union {
                    type enumeration {
                        enum not-applicable { value 0; description "Not Applicable/ Not specified."; }
                    }
                    type decimal64 {
                        fraction-digits 2;
                        range 0..80;
                    }
                }
                units "dB";
                default 'not-applicable';
                description
                    "Delta Pointloss (Rx)
                    Additional attenuation that can be determined after turning up pumps.
                    This is the fiber contribution for the pointloss: to be fine tuned in the field.
                    This additional optical attenuation may be due to e.g. bad splice at dwdm-line Rx, higher att. than 0.1 dB.
                    ";
            }

            leaf power-actual-rx {
                type ioa-l0:optical-power-actual;
                config false;
                description "Optical power received, where applicable.";
            }
        }
    }
}
