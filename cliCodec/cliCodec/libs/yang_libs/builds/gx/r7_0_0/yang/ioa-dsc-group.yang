module ioa-dsc-group {
    namespace "http://infinera.com/yang/ioa/dsc-group";
    prefix ioa-dsc-group;

    import ioa-common { prefix ioa-common; }
    import ioa-facilities-common { prefix ioa-fac-common; }

    organization "Infinera";

    contact "Infinera Technical Support <techsupport@infinera.com>";

    description "IOA YANG module defining the dsc-group facility.";

    revision "2022-12-22" {
        description "YANG Models for Infinera Open API (IOA) for release R7.0";
    }


    grouping dsc-group {
        list dsc-group {
            key name;
            description "Facility describing the dsc-group.";

            uses ioa-fac-common:facilities-common-attributes;

            uses ioa-common:arc;

            leaf carriers {
                type string { length "1..32"; }
                mandatory true;
                description "The carrier associated to this facility.
                             Possible values can be any card/resources/supported-carriers.";
            }

            leaf rate {
                type ioa-common:rate;
                mandatory true;
                description "
                    Carried signal basic rate class
                ";
            }

            leaf instance-id {
                type uint8 { range 1..max; }
                description "For identifying the dsc-group logic number, is added to the dsc-group model for creation.
                             The attribute is optional and will be automatically created if not specified.
                             The maximum value of the instance-id will be calculated based on the capacity of the line mode and the dsc-group rate
                             (ex: for creating an 100G dsc-group from 400G 16QAM line mode, instance can be between 1 and 4)";
            }

            leaf group-id {
                type uint8 { range "1..max"; }
                description "Optional parameter on dsc-group creation, specifies the dsc-group group number that the dsc is a member of for a given optical-carrier.
                             If not provided, it is automatically assigned by system.
                             (ex: for creating an 100G dsc-group from 400G 16QAM line mode, group-id can be 1/3/5/7)";
            }

            leaf pre-fec-q-sig-deg-threshold {
                type decimal64 {
                    fraction-digits 3;
                    range "0|5.600..9.600";
                }
                units dB;
                description "The threshold based on which the PRE-FEC-Q-SIGNAL-DEGRADE alarm is raised.
                             0 implies threshold crossing alarming disabled.
                             Specific sub-range is per carrier use-case.";
            }

            leaf pre-fec-q-sig-deg-hysteresis {
                type decimal64 {
                    fraction-digits 1;
                    range "0.1..1.0";
                }
                units dB;
                default 0.5;
                description "Hysteresis to account for raising of the PRE-FEC-Q-SIGNAL-DEGRADE alarm.";
            }

            leaf post-fec-q-sig-deg-threshold {
                type decimal64 {
                    fraction-digits 1;
                    range "12.5..18.0";
                }
                units dB;
                default 18.0;
                description "The threshold based on which the POST-FEC-Q-SIGNAL-DEGRADE alarm is raised.";
            }

            leaf post-fec-q-sig-deg-hysteresis {
                type decimal64 {
                    fraction-digits 1;
                    range "0.1..1.0";
                }
                units dB;
                default 0.5;
                description "Hysteresis to account for raising of the POST-FEC-Q-SIGNAL-DEGRADE alarm.";
            }

            leaf dgd-high-threshold {
                type uint16 { range "25..400"; }
                units ps;
                default 100;
                description "The threshold to raise the DGD-OORH alarm.";
            }
        }
    }
}
