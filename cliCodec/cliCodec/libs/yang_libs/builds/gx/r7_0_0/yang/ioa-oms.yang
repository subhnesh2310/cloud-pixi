module ioa-oms {
    namespace "http://infinera.com/yang/ioa/oms";
    prefix ioa-oms;

    import ioa-common { prefix ioa-common; }
    import ioa-facilities-common { prefix ioa-fac-common; }
    import ioa-l0 { prefix ioa-l0; }

    organization "Infinera";

    contact "Infinera Technical Support <techsupport@infinera.com>";

    description "IOA YANG definitions for Optical Multiplex Section (OMS) facilities.";

    revision "2023-03-31" {
        description "YANG Models for Infinera Open API (IOA) for release R6.1";
    }

    revision "2022-10-31" {
        description "YANG Models for Infinera Open API (IOA) for release R6.0";
    }

    typedef att-control-mode {
        type enumeration {
            enum not-applicable { value 0; description "Not applicable."; }
            enum auto { value 1; description "Automatic attenuation control mode in which system will decide the attenuation value."; }
            enum manual { value 2; description "Manual attenuation control mode in which target attenuation will be used."; }
        }
        description "Attenuation control mode.";
    }

    typedef grid-type {
        type enumeration {
              enum fixed-50G-96ch {
                  value 1;
                  description "50GHz fixed grid with 96 channels in C-band.";
              }
              enum fixed-100G-48ch {
                  value 2;
                  description "100GHz fixed grid with 48 channels in C-band.";
              }
              enum fixed-75G-64ch {
                  value 3;
                  description "75GHz fixed grid with 64 channels in C-band.";
              }
              enum flexible {
                  value 4; description "Flexible grid.";
              }
              enum fixed-75G-64ch-oif {
                  value 5;
                  description "75GHz fixed grid with 64 channels in C-band, OIF 400ZR standard grid.";
              }
        }
        description "Type of channel grid.";
    }

    typedef supported-band-and-grid {
        type enumeration {
              enum not-applicable {
                  value 0;
                  description "Not applicable.";
              }
              enum flexible-c-band-only {
                  value 1;
                  description "Flexible C-band without fixed-grid characterization.";
              }
              enum general-c-band {
                  value 2;
                  description "4.85THz C-band, fixed or flexi-grid.";
              }
              enum general-fixed-c-band {
                  value 3;
                  description "4.85 THz 50GHz, 75GHz or 100GHz, C-band support.";
              }
        }
        description "Supported grid modes.";
    }

    typedef type-of-oms-monitoring-mode {
        type enumeration {
            enum intrusive { value 1; description "Intrusive monitoring (TTP)"; }
            enum not-monitored { value 2; description "OMS-nim functionality, but no OCM (e.g. no DGE) required"; }
            enum non-intrusive { value 3; description "Non-intrusive, with optional monitoring (CTP)"; }
            enum dge-fixed-attenuation { value 4; description "Fixed attenuation, due to connected interstage device"; }
            enum ila-with-equalization { value 5; description "Full equalization (DGE) operation."; }
        }
        description "OMS monitoring mode (specific typedef).";
    }

    grouping oms {
        description "A re-usable grouping that formulates the basic OMS facility structure.";

        list oms {
            key "name";
            description "OMS: Optical Multiplex Section facility.";
            reference "ITU-T G.872";

            uses ioa-fac-common:facilities-common-attributes{
                refine supported-facilities {
                    max-elements 130;
               }
            }

            uses ioa-common:arc;

            leaf monitoring-mode {
                type type-of-oms-monitoring-mode;
                default intrusive;
                description "OMS monitoring mode";
                reference "ITU-T G.872; ITU-T G.876 (08/2021, prepub. Appendix III)";
            }

            leaf wss-less {
                type boolean;
                default false;
                config false;
                description "True if there is no WSS component in the Degree.";
            }

            leaf assigned-degree {
                type uint16;
                default 0;
                config false;
                description "Display degree number when card is added in modules-degree.";
            }

            uses ioa-l0:opm-optical-power-rx;

            uses ioa-l0:opm-optical-power-tx;

            leaf grid-mode {
                when "../monitoring-mode = 'intrusive'" {
                    description "Only of relevance for OMS TTP";
                }
                type grid-type;
                default 'flexible';
                description
                    "Indicates Grid type of the OMS layer.
                     - flexible: allows user to create/ delete of MC with different widths;
                     - otherwise, allows user to create MC with specific width (and delete accordingly).
                    ";
            }

            leaf grid-mode-support {
                type supported-band-and-grid;
                default 'general-c-band';
                config false;
                description
                    "Which C-band is supported, for the purpose of grid-mode configuration.";
            }

            leaf attenuation-control-mode-rx {
                when "../monitoring-mode = 'intrusive' or ../monitoring-mode = 'ila-with-equalization'" {
                    description "Only of relevance for OMS TTP or in OMS CTP with DGE (equalization).";
                }
                type att-control-mode;
                default auto;
                description "Attenuation control mode Rx (input) of the channel applicable to all channels of the OMS.";
            }

            leaf attenuation-control-mode-tx {
                when "../monitoring-mode = 'intrusive'" {
                    description "Only of relevance for OMS TTP";
                }
                type att-control-mode;
                default auto;
                description "Attenuation control mode Tx (output) of the channel applicable to all channels of the OMS.";
            }
        }
    }

    grouping oms-nim {
        description "A re-usable grouping that formulates the basic DGE Spectrum Equalization facility structure.";

        list ochm {
            key "name";
            description
                "ochm: Optical Channel non-intrusive monitoring.
                 ECDP within OMS-nim.
                ";

            uses ioa-fac-common:facilities-common-attributes;

            uses ioa-common:arc;

            leaf direction {
                type ioa-fac-common:direction;
                config false;
                description "Ingress or Egress direction";
            }

            leaf power-actual {
                type ioa-l0:optical-power-actual;
                config false;
                description "Optical Power measurement upon last OCM scan.";
            }
        }
    }

    grouping dge-equalization {
        description "A re-usable grouping that formulates the basic DGE Spectrum Equalization facility structure.";

        list spectrum {
            key "name";
            ordered-by "system";
            //ext:system-managed;
            description "OMS specific equalization within interstage access; and monitoring.";

            uses ioa-fac-common:facilities-common-attributes;
            uses ioa-common:arc;

            leaf dge-in-use {
                type boolean;
                config false;
                description "Reports true if corresponding OMS monitoring-mode is ila-with-equalization";
            }

            leaf attenuation-setting {
                type ioa-l0:type-of-attenuation;
                default 0;
                description "Entire spectrum attenuation";
            }

            list spectrum-control {
                key "direction center-frequency";
                description "DGE optical attenuation";

                leaf direction {
                    type ioa-fac-common:direction;
                    description "Ingress or Egress direction";
                }

                leaf center-frequency {
                    type ioa-l0:frequency-MHz;
                    description "Band slice center-frequency";
                    //ext-document:memo "managed by the system, cannot be changed -- except in debug.";
                }

                leaf width {
                    type ioa-l0:frequency-MHz;
                    default 0;
                    config false;
                    description "Detected width from spectrum-monitoring. 0 means unmatched.";
                }

                leaf attenuation-actual {
                    when "../../dge-in-use = 'true'" {
                        description "Only readable when Dynamic Gain Equalizer (DGE), or equivalent, is in use.";
                    }
                    type ioa-l0:attenuation-mon;
                    config false;
                    description "Actual calculated attenuation.";
                }
                leaf attenuation-target {
                    when "../../dge-in-use = 'true'" {
                        description "Only possible to configure when Dynamic Gain Equalizer (DGE), or equivalent, is in use.";
                    }
                    type ioa-l0:type-of-attenuation;
                    description "User configuration for the intended attenuation.";
                }

                leaf target-output-power {
                    type ioa-l0:optical-power-config;
                    description "The intended target output power for the spectra.";
                }
            }

            list spectrum-monitoring {
                key "direction center-frequency";
                config false;
                description "DGE optical attenuation";

                leaf direction {
                    type ioa-fac-common:direction;
                    description "Ingress or Egress direction";
                }

                leaf center-frequency {
                    type ioa-l0:frequency-MHz;
                    description "Band slice center-frequency";
                }
                leaf width {
                    type ioa-l0:frequency-MHz;
                    default 50000;
                    description "Received nmc width";
                }

                leaf lower-frequency {
                    type ioa-l0:frequency-MHz;
                    mandatory true;
                    description "Lower Frequency of a Media Channel.";
                    //ext-document:memo "managed by the system, cannot be changed -- except in debug.";
                }
                leaf upper-frequency {
                    type ioa-l0:frequency-MHz;
                    mandatory true;
                    description "Upper Frequency of a Media Channel.";
                    //ext-document:memo "managed by the system, cannot be changed -- except in debug.";
                }

                leaf target-actual-power {
                    type ioa-l0:optical-power-actual;
                    description
                        "Value: as calculated by Power Control if target-power-setting = auto.";
                }

                leaf power-actual {
                    type ioa-l0:optical-power-actual;
                    default -99;
                    description "Currently received power (-99: no power).";
                }

                leaf psd-actual {
                    type ioa-l0:actual-psd;
                    default 'not-applicable';
                    description "Currently calculated PSD. The Power Spectral Density does not depend on the spectra width.";
                }
            }
        }
    }
}
