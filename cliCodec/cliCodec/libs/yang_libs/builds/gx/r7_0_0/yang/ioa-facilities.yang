module ioa-facilities {
    namespace "http://infinera.com/yang/ioa/facilities";
    prefix ioa-fac;

    import ioa-ots { prefix ioa-ots; }
    import ioa-ots-r { prefix ioa-ots-r; }
    import ioa-osc { prefix ioa-osc; }
    import ioa-ops { prefix ioa-ops; }
    import ioa-oms { prefix ioa-oms; }
    import ioa-mc { prefix ioa-mc; }
    import ioa-nmc { prefix ioa-nmc; }
    import ioa-rsc { prefix ioa-rsc; }
    import ioa-scg { prefix ioa-scg; }
    import ioa-optical-carrier { prefix ioa-carrier; }
    import ioa-sch { prefix ioa-sch; }
    import ioa-optical-channel { prefix ioa-och; }
    import ioa-otu { prefix ioa-otu; }
    import ioa-odu { prefix ioa-odu; }
    import ioa-ethernet { prefix ioa-eth; }
    import ioa-trib-ptp { prefix ioa-trib;}
    import ioa-comm-channel { prefix ioa-cc;}
    import ioa-flexo { prefix ioa-flexo; }
    import ioa-flexo-group { prefix ioa-flexo-group; }
    import ioa-dsc { prefix ioa-dsc; }
    import ioa-dsc-group { prefix ioa-dsc-group; }
    import ioa-eth-zr { prefix ioa-eth-zr; }
    import ioa-optical-ptp { prefix ioa-optical-ptp; }
    import ioa-line-ptp { prefix ioa-line-ptp; }
    import ioa-tdm { prefix ioa-tdm; }
    import ioa-fc { prefix ioa-fc; }
    import ioa-otdr { prefix ioa-otdr; }
    import ioa-interlaken { prefix ioa-interlaken; }

    organization "Infinera";

    contact "Infinera Technical Support <techsupport@infinera.com>";

    description "IOA YANG module which acts as top level for all facilities.";

    revision "2022-10-31" {
        description "YANG Models for Infinera Open API (IOA) for release R6.0";
    }

    revision "2021-12-10" {
        description "YANG Models for Infinera Open API (IOA) for release R5.0";
    }

    revision "2021-06-01" {
        description "YANG Models for Infinera Open API (IOA) for release R4.0";
    }


    grouping facilities {

        container facilities {
            description "The top-level facility root node under which all other facilities are present.";
            uses ioa-ots:ots;
            uses ioa-ots-r:ots-r;
            uses ioa-osc:osc;
            uses ioa-ops:ops;
            uses ioa-oms:oms;
            uses ioa-oms:dge-equalization;
            uses ioa-oms:oms-nim;
            uses ioa-mc:mc;
            uses ioa-nmc:nmc;
            uses ioa-rsc:rsc;
            uses ioa-rsc:raman-pump;
            uses ioa-scg:scg;
            uses ioa-sch:sch;
            uses ioa-carrier:carrier;
            uses ioa-och:optical-channel;
            uses ioa-otu:otu;
            uses ioa-odu:odu;
            uses ioa-eth:ethernet;
            uses ioa-trib:trib-ptp;
            uses ioa-cc:comm-channel;
            uses ioa-optical-ptp:optical-ptp;
            uses ioa-otdr:otdr-ptp;
            uses ioa-line-ptp:line-ptp;
            uses ioa-flexo:flexo;
            uses ioa-flexo-group:flexo-group;
            uses ioa-dsc:dsc;
            uses ioa-dsc-group:dsc-group;
            uses ioa-eth-zr:eth-zr;
            uses ioa-tdm:oc;
            uses ioa-tdm:stm;
            uses ioa-fc:fc;
            uses ioa-interlaken:interlaken;
        }
    }
}
